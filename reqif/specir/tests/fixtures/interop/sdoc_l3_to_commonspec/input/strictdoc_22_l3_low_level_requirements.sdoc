[DOCUMENT]
MID: 6a9745098a87daf19a7c487f89f39640
TITLE: StrictDoc Low-Level Requirements Specification (L3)
VERSION: Git commit: @GIT_VERSION, Git branch: @GIT_BRANCH
DATE: @GIT_COMMIT_DATETIME
PREFIX: SDOC-LLR-
OPTIONS:
  ENABLE_MID: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: True
  - TITLE: UID
    TYPE: String
    REQUIRED: False
  - TITLE: STATEMENT
    TYPE: String
    REQUIRED: False
- TAG: REQUIREMENT
  PROPERTIES:
    VIEW_STYLE: Table
  FIELDS:
  - TITLE: MID
    TYPE: String
    REQUIRED: False
  - TITLE: UID
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[TEXT]
MID: 1ea652f0284940b6913a0a224492759f
STATEMENT: >>>
The level 3 low-level requirements specification of StrictDoc (L3/LLR) is derived from StrictDoc's L2 high-level (L2/HLR) requirements specification. The purpose of L3/LLR is to provide the lowest-level requirements from which StrictDoc's source code can be directly implemented without further information.

It is at the L3 level that the StrictDoc requirements are specified for the actual software implementers, including both the StrictDoc developers and AI agents such as Codex. At the same time, the L2/HLR requirements provide the framework for the WHAT and WHY of the implementation instructions that are specified by this L3/LLR.

NOTE: This specification level is under construction. Many L2/HLR requirements will be gradually moved to be here at the L3/HLR level.
<<<

[[SECTION]]
MID: 408105d13e234f8aa73d017404eb5349
TITLE: Markdown text markup

[REQUIREMENT]
MID: 34246811634c493dbc771ae4c8bc3b14
UID: SDOC-LLR-183
STATUS: Active
TITLE: Read Markdown markup
STATEMENT: >>>
StrictDoc shall support reading Markdown files into in-memory SDoc documents.
<<<

[REQUIREMENT]
MID: 476d094833ac4b02af1d72ad27710b36
UID: SDOC-LLR-197
STATUS: Active
TITLE: Write Markdown markup
STATEMENT: >>>
StrictDoc shall support writing in-memory SDoc documents to Markdown files.
<<<

[REQUIREMENT]
MID: bc3b1411634c493dbc771ae4c8bc3b14
UID: SDOC-LLR-192
STATUS: Active
TITLE: Markdown files discovery
STATEMENT: >>>
StrictDoc shall discover Markdown files ``*.md`` and ``*.markdown`` using the same mechanism as used for SDoc files.
<<<

[REQUIREMENT]
MID: 245378eed60245378de2e099facd196d
UID: SDOC-LLR-196
STATUS: Active
TITLE: Identical Markdown content by import/export roundtrip
STATEMENT: >>>
StrictDoc shall ensure that identical Markdown content is produced every time StrictDoc reads a Markdown file and then writes it to another Markdown file.

The following aspects shall additionally apply:

- For MVP, line-endings should support both LF (Linux/macOS-style) and CRLF (Windows-style).
- The ``export --formats=markdown`` shall work for any format readable by StrictDoc, including Markdown itself, SDoc, RDF (future growth), ReqIF, etc.

NOTE: The write-back to Markdown file must happen through proper AST serialization, not just by giving back the original read Markdown source.

Exceptions:

Edge cases related to handling non-default input formats are postponed after the Markdown MVP is implemented. For example:

- Markdown reader encounters content format #3 (implicit field) via [LINK: SDOC-LLR-185], but writer always emits #1/#2 for content via [LINK: SDOC-LLR-198]. In this case the content will not be identical, but it is accepted for an MVP implementation.
<<<
RATIONALE: >>>
A consistent import/export roundtrip implementation and testing reduces the risk of the Markdown bi-directional import/export corruption.
<<<

[REQUIREMENT]
MID: 11634c11634c493dbc771ae4c8bc3b14
UID: SDOC-LLR-191
STATUS: Active
TITLE: Markdown formats
STATEMENT: >>>
StrictDoc shall rely only on CommonMark core syntax v0.31.2 for SDoc node recognition.
<<<
RATIONALE: >>>
CommonMark core is the most portable target across parsers.
<<<

[REQUIREMENT]
MID: 41351111634c493dbc771ae4c8bc3b14
UID: SDOC-LLR-186
STATUS: Active
TITLE: Meta fields vs content fields
STATEMENT: >>>
StrictDoc shall recognize the following Markdown nodes as SDoc nodes:

.. code-block:: markdown

    ### Node title
    (empty line)
    **Meta field name 1**:
    **Meta field name 2**:
    ...
    (empty line)
    **Note content field 1**: ...
    (empty line)
    **Note content field 2**: ...
    ...

An SDoc node terminates when another Markdown section header or an EOF is encountered.

NOTE: There are no limitations to node level. A Markdown node can be at level 2, 3, etc. The level 1 is served for a root document node (document title with optional fields).
<<<

[REQUIREMENT]
MID: 54321111634c493dbc771ae4c8bc3b14
UID: SDOC-LLR-189
STATUS: Active
TITLE: One Markdown file — One SDoc document
STATEMENT: >>>
StrictDoc shall parse Markdown files using the "one Markdown file — one SDoc document" principle.
<<<

[REQUIREMENT]
MID: 12111111634c493dbc771ae4c8bc3b14
UID: SDOC-LLR-195
STATUS: Active
TITLE: Strict ban for redundant empty lines
STATEMENT: >>>
When a parsing Markdown file, if StrictDoc encounters two or more consecutive empty lines and the lines are not within a Markdown code block or a Markdown blockquote block, StrictDoc shall raise a StrictDocSemanticError.

NOTE: Empty lines includes whitespace-only lines which StrictDoc shall ban as well.
<<<

[REQUIREMENT]
MID: 999f59ede0f2477181bfc7667684df59
UID: SDOC-LLR-194
STATUS: Active
TITLE: Syntax for meta and content field names
STATEMENT: >>>
StrictDoc shall recognize the meta and content field names according to the following rules:

- Format is: ``**Field name**:``.
- Alphanumeric character range, separated by spaces, underscores or dashes.

Examples:

- ``**Statement**:``
- ``**STATEMENT**:``
- ``**IMPORTANT_STATEMENT**:``
- ``**SPDX-Req-ID**:``
<<<

[REQUIREMENT]
MID: 69f077ede0f2477181bfc7667684df59
UID: SDOC-LLR-184
STATUS: Active
TITLE: Three conventions for meta fields
STATEMENT: >>>
StrictDoc shall support reading out SDoc nodes out of Markdown sections arranged in the following way:

1) Requirements with meta-information stored in bullet point list:

.. code-block:: markdown

    ### Requirement title

    - **MID**: abcdabcdabcdabcdabcdabcdabcdabcdabcd
    - **UID**: REQ-001
    - **Status**: Draft

     System A shall do B.

When a Markdown title is followed by a full empty line followed by a bullet list and the bullet list follows the format ``- **<Name>**: <Value>``, the bullet list must be treated as a list of meta fields. The bullet list is terminated by one empty line.

2) Requirements with meta-information stored in consecutive lines separated by the "\\" character:

.. code-block:: markdown

    ### Requirement title

    **MID**: abcdabcdabcdabcdabcdabcdabcdabcdabcd \
    **UID**: REQ-001 \
    **Status**: Draft

    System A shall do B.

When a Markdown title is followed by a full empty line followed by list of lines in the format ``**<Name>**: <Value> \``, the list must be treated as a list of meta fields.
The line list is terminated by one empty line. The last line shall not end with a "\" character.

3) Requirements with meta-information stored in consecutive lines separated by the two empty space characters (as officially supported by Markdown):

.. code-block:: markdown

    ### Requirement title

    **MID**: abcdabcdabcdabcdabcdabcdabcdabcdabcd<two spaces>
    **UID**: REQ-001<two spaces>
    **Status**: Draft<two spaces>

    System A shall do B.

When a Markdown title is followed by a full empty line followed by list of lines in the format ``**<Name>**: <Value><two spaces>``, the list must be treated as a list of meta fields. The list is terminated by one empty line.

Each given node must follow only one of these three syntaxes. If StrictDoc encounters that a single node has more one or more fields of a mixed style, it must give up parsing this node as a valid node, and treat it as a non-normative SECTION/TEXT node.

As of Markdown MVP, the default and preferred syntax: shall be #2 with backslashes.
<<<

[REQUIREMENT]
MID: 111111ede0f2477181bfc7667684df59
UID: SDOC-LLR-185
STATUS: Active
TITLE: Valid formats for multi-line fields
STATEMENT: >>>
StrictDoc shall recognize SDoc node multiline fields from the following three formats

1) Explicit field name:

.. code-block:: markdown

    ### Requirement title

    - **MID**: abcdabcdabcdabcdabcdabcdabcdabcdabcd

     **Statement**: System A shall do B.

2) Explicit field name with a line break:

.. code-block:: markdown

    ### Requirement title

    - **MID**: abcdabcdabcdabcdabcdabcdabcdabcdabcd

     **Statement**:

     System A shall do B.

3) Implicit field name with a line break:

.. code-block:: markdown

    ### Requirement title

    **MID**: abcdabcdabcdabcdabcdabcdabcdabcdabcd

    System A shall do B.

    **Rationale**: This requirement is important because XYZ.

In this case, StrictDoc shall recognize the ``System A shall do B.`` as if it was written as ``**Statement**: System A shall do B.`` and recognize the rationale part as an explicitly written multiline field.

As of Markdown MVP, the default and preferred syntax shall be:

- #1 for values with single-line or single-paragraph/block strings.
- #2 for values with multiple markdown blocks separated by full empty lines.
<<<

[REQUIREMENT]
MID: 121eb00caee34e3fa6eaa683f211a472
UID: SDOC-LLR-202
STATUS: Active
TITLE: Support node parent relations
STATEMENT: >>>
StrictDoc shall support node relations in Markdown using the meta field:

.. code-block:: markdown

    **Relations**: <UID-1>, <UID-2>, ...

When reading Markdown:
- Each UID from the Relations field shall be converted to a relation with TYPE: Parent and VALUE: <UID>.
- All extra spaces shall be normalized before parsing to canonical ``<UID-1>, <UID-2>, ...``.
- The Markdown reader shall not check whether any UID actually exists. This task is deferred to the traceability index builder.

When writing Markdown, SDoc node relations with TYPE: Parent and no ROLE shall be serialized back to the same Relations field as a comma-separated UID list.

NOTE: For MVP, relation roles and Child relation types are out of scope.

NOTE: If the Relations field is not placed as the meta field but as the content field, StrictDoc shall raise a ``StrictDocSemanticError``.
<<<

[REQUIREMENT]
MID: 84df59ede0f2477181bfc7667684df59
UID: SDOC-LLR-193
STATUS: Active
TITLE: Valid SDoc node criteria
STATEMENT: >>>
StrictDoc shall recognize a Markdown node as a valid SDoc node when the Markdown node meets the following criteria:

- The node has one of the meta-fields: MID or UID.
- The node has an explicit or implicit content field.
- All node fields, meta or content, have a valid syntax.
- All node fields, meta or content, are valid default SDoc grammar fields.
<<<

[REQUIREMENT]
MID: 2f3a565aa60340369689eef45cbe7c9c
UID: SDOC-LLR-200
STATUS: Active
TITLE: Valid SDoc document root node
STATEMENT: >>>
StrictDoc shall recognize a root Markdown node as a valid SDoc document node when the said Markdown node meets the following criteria:

- The node has zero or more valid meta-fields.
- The valid metafields must satisfy [LINK: SDOC-LLR-194] and be formatted according to one meta syntax from [LINK: SDOC-LLR-184].

**Example: Valid DOCUMENT (title and metadata) + SECTION:**

.. code-block:: markdown

    # Document title

    **MID**: abcdabcdabcdabcdabcdabcdabcdabcdabcd \
    **UID**: DOC-001 \
    **Author**: John Doe

    ## Hello world

Such a description shall translate to an SDoc document with:

- DOCUMENT node with a title "Document title" and meta fields (MID, UID, Author).
- SECTION node with a title "Hello world".

**Example: Valid DOCUMENT (title and metadata) + TEXT:**

.. code-block:: markdown

    # Document title

    **MID**: abcdabcdabcdabcdabcdabcdabcdabcdabcd \
    **UID**: DOC-001 \
    **Author**: John Doe

    Hello world.

Such a description shall translate to an SDoc document with:

- DOCUMENT node with a title "Document title" and meta fields (MID, UID, Author).
- TEXT node with a statement "Hello world.".

**Example: Valid DOCUMENT (title, no metadata) + TEXT:**

.. code-block:: markdown

    # Document title

    MID: abc

    Hello world.

Such a description shall translate to an SDoc document with:

- DOCUMENT node with a title "Document title" and no meta fields.
- TEXT node with a statement "MID: abc\\n\\nHello world.".
<<<

[REQUIREMENT]
MID: 11133111634c493dbc771ae4c8bc3b14
UID: SDOC-LLR-190
STATUS: Active
TITLE: Reading rules — Default grammar for MVP
STATEMENT: >>>
When a parsing Markdown file, StrictDoc shall generate an SDoc document using the default SDoc grammar according to the following rules:

- The only supported node for MVP shall be REQUIREMENT, TEXT and SECTION nodes with no other nodes supported.
- A valid SDoc node shall be recognized as REQUIREMENT. The Markdown's node title becomes the REQUIREMENT node's TITLE.
- If a Markdown node cannot be recognized as a valid SDoc node, the node shall recognize the said Markdown node's title as a SECTION node with a TITLE field set to the title and the node's body as a regular (non-normative) TEXT SDoc node, not as a normative SDoc node. The TEXT node's statement shall contain the Markdown node's body.
- All field names shall be capitalized when created to SDoc field objects. For example, ``Statement`` becomes ``STATEMENT``. At the same time, the original field names must be written to the document's grammar as-is. For example, a ``**Rationale**:`` becomes ``RATIONALE`` in the SDoc field name and ``Rationale`` in the human title.
- StrictDoc shall defer the validation of MID/UID uniqueness across nodes to the TraceabilityIndexBuilder class.
- If a given field name appears more than once in a node, StrictDoc shall raise a StrictDocSemanticError.
- If a node is otherwise invalid and also has duplicate fields, the parser shall treat this node as SECTION and TEXT without raising errors.
- All SDoc node fields, REQUIREMENT/TEXT/SECTION, must store all field values' Markdown content verbatim, without any pre-processing. This includes preserving original whitespace/line endings exactly.
<<<

[REQUIREMENT]
MID: 44c2dffd898345f39a384bcdacc01b5e
UID: SDOC-LLR-199
STATUS: Active
TITLE: Reading rules — Node hierarchy
STATEMENT: >>>
When a parsing Markdown file, StrictDoc shall generate an SDoc document using the default SDoc grammar according to the following rules:

- The first content of a Markdown file shall always be a level 1 ``#`` node with the document title, followed by an optional set of metafields that translate to SDoc document meta (DocumentConfig/custom_metadata). The syntax for metafields shall be the same to meta fields of a regular markdown node. For MVP, all metafields shall be written as custom_metadata, with no reserved fields are considered.

- When the root L1 document title node with (optional meta fields) are recognized, StrictDoc shall treat all following text as a TEXT node until any other header node starts.

- If StrictDoc can recognize the root L1 document node title but no valid metadata, StrictDoc shall treat all following text as a TEXT node until any other header node starts.

- When root metadata has a valid syntax but has invalid semantics (duplicated fields), StrictDoc shall raise StrictDocSemanticError.

- No other node can be at level 1 except the document title, otherwise StrictDocSemanticError must be raised.

- The Markdown node hierarchy shall be strictly consecutive in forward direction:

  - If a node level forward jump is encountered, for example L1->L3, StrictDoc shall raise a StrictDocSemanticError, regardless of whether the node is valid SDoc node or invalid.

- The node level jumps in backward direction, for example L4->L2, are allowed if the node with a lower level results at level 2 or higher.
<<<

[REQUIREMENT]
MID: c144739494ad4f75b65b9286248005eb
UID: SDOC-LLR-198
STATUS: Active
TITLE: Writing rules — Default grammar for MVP
STATEMENT: >>>
When writing an SDoc document to a markdown file, StrictDoc shall generate the Markdown markup according to the following rules:

- The meta fields shall be written:

  - Using the format #2 for new documents not coming from file system (using backslashes for all meta-field lines but last one).
  - Using the format that was auto-detected during reading a Markdown file in case the file is already on the disk and follows a certain convention. The detection shall be detected at a file level and memorized individually by each SDoc document.

- The content fields shall be written using formats #1 (Explicit field name) for single-paragraph fields and #2 (Explicit field name with a line break) for multi-paragraph fields. A multi-paragraph field is one that results in multiple markdown paragraphs/blocks each separated visually by a full empty line.

- StrictDoc shall write the SDoc fields as Markdown fields based on SDoc human title as recorded in the document grammar element field human title. If a human title is missing in the grammar, the field name shall be used.

- All fields shall be printed in the same order like they are stored in an SDoc node. Meta vs content decision shall be based on a standard SDocNode/GrammarElement decision for multiline index.

- The node level shall be used for defining the Markdown node level. The document title becomes the top-level section level 1. SDoc node level 1 becomes ``##``, level 2 becomes ``###``, etc.
<<<

[REQUIREMENT]
MID: 987111ede0f2477181bfc7667684df59
UID: SDOC-LLR-187
STATUS: Active
TITLE: Robust Markdown backend
STATEMENT: >>>
StrictDoc shall employ a well-maintained Markdown library with Python support.
<<<

[[/SECTION]]

[[SECTION]]
MID: 65cfed23d9bb404cad88dadc95feb0d1
TITLE: HTML2PDF export

[REQUIREMENT]
MID: 95f0e0198d8446a38eb1c7fc0f409522
UID: SDOC-LLR-203
TITLE: Use of html2pdf4doc
STATEMENT: >>>
StrictDoc shall export HTML documents using html2pdf4doc library with the following document types supported already:

- StrictDoc's main DOC document type/screen.
<<<
RATIONALE: >>>
html2pdf4doc is part of the StrictDoc project that is developed by the core team. It allows printing PDF pages directly from StrictDoc HTML and gives the developers a full control over the printing mechanics.
<<<

[REQUIREMENT]
MID: 335b11da872245c0bf09c82d5909db0e
UID: SDOC-LLR-204
STATUS: Active
TITLE: Use of PyPDF for PDF postprocessing
STATEMENT: >>>
StrictDoc shall employ the PyPDF library for the following tasks:

- Rewriting all StrictDoc's LINK/ANCHOR to documents of the same project tree into the PDF anchors.
<<<
RATIONALE: >>>
The extra processing with PyPDF is needed because there are limitations of what developers can do when printing HTML to PDF with html2pdf4doc based on Google Chrome Driver.
<<<

[REQUIREMENT]
MID: 272338e1e8f244eca573348660464b09
UID: SDOC-LLR-205
STATUS: Active
TITLE: Cross-linking PDF documents from one project tree
STATEMENT: >>>
When exporting HTML documents to PDF, StrictDoc shall rewrite all LINK/ANCHOR to documents of the same project tree into the PDF document links/anchors according to the following rule:

- The Chrome Driver resolves the relative links to other documents with full paths, e.g., ``file:///<full-path-to-another-SDoc-document>-PDF.html#<anchor>``.
- The PDF postprocessing step shall convert these absolute ``file:///...` links to just relative paths: ``<relative-path-to-another-SDoc-document>.pdf`` without the leading slash character.
- If one PDF is in a nested folder compared to another PDF, the link to this PDF anchor shall have relative ``../`` path components.
<<<
RATIONALE: >>>
Allows a reader to navigate between PDF documents of the same project as requested by the parent requirement.
<<<
COMMENT: >>>
The PDF cross-document linking is supported by the PDF format natively but is known to not work in all PDF viewers. For example, it is known to work well in Linux PDF viewers, but not macOS Preview viewer.
<<<

[[/SECTION]]
