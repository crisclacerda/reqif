# Documentation export by StrictDoc

# Specification: StrictDoc High-Level Requirements (L2)

## R1: SDoc data model (SECTION)

### SDOC-SRS-18: Data model (REQUIREMENT)
StrictDoc shall be based on a data model.
- STATUS: Active
- RATIONALE: Designing StrictDoc with a goal of having a consistent data model ensures that the tool:

  1) can support a rich set of use cases,
  2) model the existing documentation templates used by the industries,
  3) interface well with other formats for storing documentation and requirements, e.g., ReqIF and SPDX.
- NOTES: Verification: data model diagram TBD.

### SDOC-SRS-26: Requirement model (REQUIREMENT)
StrictDoc's data model shall support modeling requirements.
- STATUS: Active

### SDOC-SRS-100: Requirement model fields (REQUIREMENT)
StrictDoc's "Requirement" model shall support configurable fields system.
- STATUS: Active

### SDOC-SRS-132: Requirement model default fields (REQUIREMENT)
By default, the Requirement shall support the following fields:

- MID
- UID
- STATUS
- TITLE
- STATEMENT
- RATIONALE
- COMMENT.
- STATUS: Active
- RATIONALE: These fields are the most typical fields found in requirement documents.

### SDOC-SRS-98: Document model (REQUIREMENT)
StrictDoc's data model shall support modeling documents.
- STATUS: Active

### SDOC-SRS-110: Document metadata (REQUIREMENT)
StrictDoc's data model shall support a Document metadata model including at least:

- UID
- Document version
- Document classification
- Document authors.
- STATUS: Active

### SDOC-SRS-151: Document configuration (REQUIREMENT)
StrictDoc's data model shall support configuring the document options:

- Enable/disable MID
- Markup choice, e.g., RST, HTML, etc.
- Levels (automatic or manual)
- Node style
- Default presentation view.
- STATUS: Active

### SDOC-SRS-99: Section model (REQUIREMENT)
StrictDoc's data model shall support a concept of a "Section" which nests other Sections, Requirements, Texts.
- STATUS: Active
- RATIONALE: "Section" corresponds to a chapter or a section in a document and helps to organize a document by grouping text nodes, requirements and other sections.

### SDOC-SRS-135: Free text (REQUIREMENT)
StrictDoc's data model shall support a "Free Text" model, representing non-normative documentation content.
- STATUS: Active
- RATIONALE: Documentation comprises normative components, such as uniquely identifiable elements like requirements or design items, and non-normative components, including introductory text, overview chapters, and other content. The non-normative parts help provide a general understanding for the reader but do not contribute to traceability information. StrictDoc's free text is designed to store this type of non-normative information in SDoc documents.

### SDOC-SRS-109: Composeable document (REQUIREMENT)
StrictDoc's data model shall allow composing a Document from other Documents.
- STATUS: Active
- RATIONALE: The logic behind the parent requirement remains fully relevant. Additionally, an alternative approach could involve using a dedicated entity, like "Fragment", to allow a Document to be composed of includable sections or document fragments. Managing composition at the Document level eliminates the need in additional entities like "Fragment", streamlining both the conceptual understanding and the practical implementation of composability.
- NOTES: The corresponding UI capability for Fragments CRUD is TBD.

### SDOC-SRS-31: Requirement relations (REQUIREMENT)
The StrictDoc data model shall support connecting requirements using Parent and Child relations.
- STATUS: Active
- RATIONALE: Support of both Parent and Child relations allows to build typical requirements relations such as child-to-parent and less common relations when one document can have parent links to a parent document and child links to a child document (e.g., the so-called "compliance" or "tailoring matrix" documents may use this structure).

### SDOC-SRS-101: Requirement relation roles (REQUIREMENT)
Each SDoc relation shall be optionally configurable with a relation role.

NOTE: A relation role is a string value. Typical examples: "refines", "verifies", "implements".
- STATUS: Active

### SDOC-SRS-149: Inline links (REQUIREMENT)
StrictDoc shall support referencing any node by embedding a hyperlink within the text content of another node.
- STATUS: Active
- RATIONALE: The inline links do not replace the relations between SDoc nodes. Instead, an inline link could be an easy way to refer from one textual node to a chapter or a document. A common use case is "See section ABC for more details".

### SDOC-SRS-150: Inline anchors (REQUIREMENT)
StrictDoc shall support adding anchors within the text content of any node, such that these anchors can be referenced by inline links from other nodes.
- STATUS: Active
- RATIONALE: Anchors allow authors to define precise reference points within SDoc node fields.

## R16: SDoc text markup (SECTION)

### SDOC-SRS-20: SDoc markup language (REQUIREMENT)
StrictDoc shall implement its own text markup language called S-Doc (strict-doc).
- STATUS: Active
- RATIONALE: The most commonly used Markdown format lacks the ability to store requirements metadata. While the RST syntax does allow for customization with directives to implement metadata extensions, its visual appearance contradicts other requirements of StrictDoc, such as the type-safety of the grammar and visual readability. Therefore, a markup language tailored specifically to the needs of the requirements tool provides direct control over the capabilities implemented in both the markup and the user interface.

### SDOC-SRS-136: Identical SDoc content by import/export roundtrip (REQUIREMENT)
StrictDoc shall ensure that identical SDoc content is produced every time StrictDoc reads an SDoc file and then writes it to another SDoc file.
- STATUS: Active
- RATIONALE: A consistent import/export roundtrip implementation and testing reduces the risk of the SDoc bi-directional import/export corruption.

### SDOC-SRS-127: SDoc and Git storage (REQUIREMENT)
StrictDoc shall assume and implement capabilities for storage of SDoc files using Git version control system.
- STATUS: Active

### SDOC-SRS-104: SDoc file extension (REQUIREMENT)
The SDoc markup content shall be stored in files with .sdoc extension.
- STATUS: Active
- RATIONALE: Given that the name of the model is S-Doc (strict-doc), it is reasonable to make the document files have the ``.sdoc`` extension. This helps to identify the document files.

### SDOC-SRS-105: One document per one SDoc file (REQUIREMENT)
StrictDoc's SDoc file shall represent content of a single document.
- STATUS: Active
- NOTES: A "Document" corresponds to a "Document" of the SDoc data model.

### SDOC-SRS-19: Fixed grammar (REQUIREMENT)
StrictDoc's markup language shall be based on a well-defined grammar.
- STATUS: Active

### SDOC-SRS-93: Default grammar fields (REQUIREMENT)
The StrictDoc grammar shall have at least the following fields activated by default:

- UID
- STATUS
- TITLE
- STATEMENT
- RATIONALE
- COMMENT
- RELATIONS (references to other requirements)
- STATUS: Active

### SDOC-SRS-21: Custom grammar / fields (REQUIREMENT)
The SDoc markup shall support custom grammars.
- STATUS: Active
- RATIONALE: A custom grammar allows a user to define their own configuration of requirement fields.

### SDOC-SRS-122: Importable grammars (REQUIREMENT)
StrictDoc shall support an inclusion of a grammar stored in a separate file.
- STATUS: Active
- RATIONALE: A single grammar defined for several documents helps to standardize the structure of all documents in a documentation tree and removes the effort needed to create identical grammars all the time.

### SDOC-SRS-22: UID identifier format (REQUIREMENT)
The SDoc markup shall only accept UID identifiers that consist of alphanumeric characters separated by a limited set of ("_", "-", ".") characters (TBD).
- STATUS: Active
- RATIONALE: A standardized UID format supports easier unique identification of requirements. It is easier to visually identify UIDs that look similar and common to a given industry.
- NOTES: This requirement may need a revision to accommodate for more UID formats.

### SDOC-SRS-24: Format-specific markup-to-HTML fragment writers (REQUIREMENT)
StrictDoc shall render supported markup formats (at least RST and Markdown) to HTML fragments via dedicated format-specific writers selected by markup type.
- STATUS: Active

### SDOC-SRS-27: MathJAX (REQUIREMENT)
StrictDoc's markup language shall support integration with MathJax.
- STATUS: Active

### SDOC-SRS-23: No indentation (REQUIREMENT)
SDoc text markup blocks shall all start from column 1, i.e., the nesting of the blocks is not allowed.
- STATUS: Active
- RATIONALE: Nesting large text blocks of free text and requirements compromises readability.

### SDOC-SRS-25: Type-safe fields (REQUIREMENT)
SDoc markup shall provide "type safety" for all fields.

NOTE: "Type safety" means that each field has a type and a corresponding set of validation checks.
- STATUS: Active

## R31: Markdown markup (SECTION)

### SDOC-SRS-202: Markdown support (REQUIREMENT)
StrictDoc shall support Markdown markup.
- STATUS: Active
- RATIONALE: Markdown is the most popular markup language among programmers. Compared to the StrictDoc native SDoc markup, Markdown is much more familiar to developers, which lowers the entry barrier for writing formal requirements with StrictDoc or other tools. It is also used extensively by AI tools.

## SECTION-SRS-Graph-database: Graph database (SECTION)

### SDOC-SRS-28: Traceability index (REQUIREMENT)
StrictDoc shall maintain a complete Traceability Index of all documentation- and requirements-related information available in a project tree.
- STATUS: Active

### SDOC-SRS-29: Uniqueness UID in tree (REQUIREMENT)
For each requirement node, the Traceability Index shall ensure its uniqueness throughout the node's lifecycle.
- STATUS: Active
- RATIONALE: The requirement ensures that the Traceability Index takes of care of validating the uniqueness of all nodes in a document/requirements graph.

### SDOC-SRS-30: Detect links cycles (REQUIREMENT)
The Traceability Index shall detect cycles between requirements.
- STATUS: Active

### SDOC-SRS-32: Link document nodes (REQUIREMENT)
The Traceability Index shall recognize and maintain the relations between all documents of a project tree.
- STATUS: Active
- RATIONALE: The relations between all documents are a summary of all relations between these documents' requirements. This information is useful for:

  1) Structural analysis of a requirements/documents graph.
  2) Incremental regeneration of only those documents whose content was modified.

### SDOC-SRS-102: Automatic resolution of reverse relations (REQUIREMENT)
The StrictDoc's graph database shall maintain the requirement relations and their reverse relations as follows:

- For a Parent relation, the database shall calculate the reverse Child relation.
- For a Child relation, the database shall calculate the reverse Parent relation.
- STATUS: Active
- RATIONALE: The calculation of the reverse relations allows the user interface code to get and display both requirement's parent and child relations.
- NOTES: Example: If a child requirement REQ-002 has a parent requirement REQ-001, the graph database first reads the link ``REQ-002 -Parent> REQ-001``, then it creates a corresponding ``REQ-001 -Child> REQ-002`` on the go. Both relations can be queried as follows, in pseudocode:

  .. code-block::

      get_parent_requirements(REQ-002) == [REQ-001]
      get_children_requirements(REQ-001) == [REQ-002]

## R39: Documentation tree (SECTION)

### SDOC-SRS-115: Finding documents recursively (REQUIREMENT)
StrictDoc shall discover SDoc documents recursively based on a specified input path.
- STATUS: Active
- RATIONALE: Recursive search allows working with documents located in multiple folders, potentially spanning over several Git repositories.

## SECTION-SRS-Web-HTML-frontend: Web/HTML frontend (SECTION)

### SECTION-SRS-General-export-requirements-2: General export requirements (SECTION)

#### SDOC-SRS-49: Export to static HTML website (REQUIREMENT)
StrictDoc shall support generating requirements documentation into static HTML.
- STATUS: Active

#### SDOC-SRS-50: Web interface (REQUIREMENT)
StrictDoc shall provide a web interface.
- STATUS: Active

#### SDOC-SRS-123: Multi-user editing of documents (REQUIREMENT)
StrictDoc shall support concurrent use and editing of a single StrictDoc web server instance by multiple users.
- STATUS: Active

#### SDOC-SRS-48: Preserve generated file names (REQUIREMENT)
For all export operations, StrictDoc shall maintain the original filenames of the documents when producing output files.
- STATUS: Active
- RATIONALE: Name preservation helps to visually identify which input file an output file corresponds to.

### SECTION-SRS-Screen-Project-tree: Screen: Project tree (SECTION)

#### SDOC-SRS-53: View project tree (REQUIREMENT)
StrictDoc's "Project tree" screen shall provide browsing of a documentation project tree.
- STATUS: Active
- RATIONALE: This screen is the main tool for visualizing the project tree structure.

#### SDOC-SRS-107: Create document (REQUIREMENT)
StrictDoc's Project Tree screen shall allow creating documents.
- STATUS: Active

#### SDOC-SRS-108: Delete document (REQUIREMENT)
StrictDoc's Project Tree screen shall allow deleting documents.
- STATUS: Active

### SECTION-SRS-Screen-Document-DOC: Screen: Document (DOC) (SECTION)

#### SDOC-SRS-201: Format-specific document handling (REQUIREMENT)
StrictDoc's Document screen shall arrange all CRUD operations according to the input document format.

Example: If an SDoc document is read from a Markdown file using a dedicated reader, it shall be written back using a Markdown writer.
- STATUS: Active

#### SDOC-SRS-54: Read document (REQUIREMENT)
StrictDoc's Document screen shall allow reading documents.
- STATUS: Active

#### SDOC-SRS-106: Create node (REQUIREMENT)
StrictDoc's Document screen shall allow creating document nodes.
- STATUS: Active

#### SDOC-SRS-161: Clone node from existing node (REQUIREMENT)
StrictDoc shall support cloning nodes from existing nodes.
- STATUS: Active
- RATIONALE: Simplifies the creation of similar nodes.

#### SDOC-SRS-55: Update node (REQUIREMENT)
StrictDoc's Document screen shall allow update document content.
- STATUS: Active

#### SDOC-SRS-162: Delete node (REQUIREMENT)
StrictDoc's Document screen shall support the deletion of document nodes.
- STATUS: Active

#### SDOC-SRS-159: Create node relation (REQUIREMENT)
StrictDoc's Document screen shall creating updating node relations.
- STATUS: Active

#### SDOC-SRS-158: Update node relation (REQUIREMENT)
StrictDoc's Document screen shall allow updating node relations.
- STATUS: Active

#### SDOC-SRS-92: Move requirement / section nodes within document (REQUIREMENT)
StrictDoc's Document screen shall provide a capability to move the nodes within a document.
- STATUS: Active
- RATIONALE: Moving the nodes within a document is a convenience feature that speeds up the requirements editing process significantly.

#### SDOC-SRS-56: Edit Document grammar (REQUIREMENT)
StrictDoc's screen shall allow editing a document's grammar.
- STATUS: Active
- RATIONALE: Editing document grammar allows a user to customize the requirements fields.

#### SDOC-SRS-57: Edit Document options (REQUIREMENT)
StrictDoc's Document screen shall provide controls for configuring the document-specific options.
- STATUS: Active

#### SDOC-SRS-96: Auto-generate requirements UIDs (REQUIREMENT)
StrictDoc's Document screen shall provide controls for automatic generation of requirements UIDs.
- STATUS: Active

#### SDOC-SRS-120: Auto-completion for requirements UIDs (REQUIREMENT)
StrictDoc's Document screen shall provide controls for automatic completion of requirements UIDs.
- STATUS: Active
- NOTES: The automatic completion can be especially useful when a user has to fill in a parent relation UID.

#### SDOC-SRS-59: Buttons to copy text to buffer (REQUIREMENT)
StrictDoc shall provide a "copy text to buffer" button for all requirement's text fields.
- STATUS: Active

### SECTION-SRS-Screen-Table-TBL: Screen: Table (TBL) (SECTION)

#### SDOC-SRS-62: View TBL screen (REQUIREMENT)
StrictDoc's Table screen shall allow reading documents in a table-like manner.
- STATUS: Active

### SECTION-SRS-Screen-Traceability-TR: Screen: Traceability (TR) (SECTION)

#### SDOC-SRS-65: View TR screen (REQUIREMENT)
StrictDoc shall provide a single document-level traceability screen.

NOTE: This screen helps to read a document like a normal document while the traceability to this document's parent and child elements is visible at the same time.
- STATUS: Active

### SECTION-SRS-Screen-Deep-traceability-DTR: Screen: Deep traceability (DTR) (SECTION)

#### SDOC-SRS-66: View DTR screen (REQUIREMENT)
StrictDoc shall provide a deep traceability screen.
- STATUS: Active

### R72: Screen: HTML2PDF (SECTION)

#### SDOC-SRS-51: Export to HTML content to PDF (HTML2PDF) (REQUIREMENT)
StrictDoc shall allow exporting documents and entire documentation trees to PDF.
- STATUS: Active
- RATIONALE: As required by the parent requirement, PDF is one of the most common documentation formats.

#### SDOC-SRS-203: Cross-linking PDF documents from same project tree (REQUIREMENT)
When exporting multiple HTML documents from a same project tree into PDF, StrictDoc shall preserve all cross-document linking in the output PDF documents.
- STATUS: Active
- RATIONALE: This enables navigation between PDF documents within the same project tree, which can be useful for simplifying the review and tracing work performed by readers.

#### SDOC-SRS-160: Custom PDF export template (REQUIREMENT)
StrictDoc shall support the customization of the PDF export template.
- STATUS: Active

### R76: Screen: Project statistics (SECTION)

#### SDOC-SRS-97: Display project statistics (REQUIREMENT)
StrictDoc shall provide a Project Statistics screen that displays the following project information:

- Project title
- Date of generation
- Git revision
- Total documents
- Total requirements
- Requirements status breakdown
- Total number of TBD/TBC found in documents.
- STATUS: Active
- RATIONALE: TBD

#### SDOC-SRS-154: Support for user-provided custom statistics generators (REQUIREMENT)
StrictDoc shall support customization of the project statistics screen, enabling users to define and display their own project-specific statistics.
- STATUS: Active
- RATIONALE: Projects often have unique traceability and reporting requirements, and supporting custom statistics allows StrictDoc to display metrics that are most relevant to each project's context.

### R79: Screen: Document tree map (SECTION)

#### SDOC-SRS-157: Tree map (REQUIREMENT)
StrictDoc shall provide a tree map screen, visualizing the following information:

- Document tree map
- Requirements coverage by source code
- Requirements coverage by test files.
- STATUS: Active
- RATIONALE: Enables the visualization and browsing of the overall document tree and requirements coverage information.

### R81: Screen: Source coverage (SECTION)

#### SDOC-SRS-35: Project source code coverage (REQUIREMENT)
StrictDoc shall generate project source code coverage information.

NOTE: Source code information can be visualized using both web or CLI interfaces.
- STATUS: Active

### R83: Screen: Single source file coverage (SECTION)

#### SDOC-SRS-36: Single source file coverage (REQUIREMENT)
StrictDoc shall generate single file traceability information.
- STATUS: Active
- RATIONALE: With this capability in place, it is possible to focus on a single implementation file's links to requirements which helps in the code reviews and inspections.

### R85: Screen: Traceability matrix (SECTION)

#### SDOC-SRS-112: Traceability matrix (REQUIREMENT)
StrictDoc shall provide a traceability matrix screen.
- STATUS: Active

### R87: Screen: Project tree diff (SECTION)

#### SDOC-SRS-111: Project tree diff (REQUIREMENT)
StrictDoc shall provide a project tree diff screen.
- STATUS: Active

### R89: Content search (SECTION)

#### SDOC-SRS-155: Content search (REQUIREMENT)
StrictDoc shall provide searching documentation content with queries via a search bar.
- STATUS: Active
- RATIONALE: As per the parent requirement, a search bar with query support enables users to interactively find specific content without navigating the entire documentation tree.

## SECTION-SRS-Requirements-to-source-traceability: Requirements-to-source traceability (SECTION)

### SDOC-SRS-33: Link requirements with source files (REQUIREMENT)
StrictDoc shall support bi-directional linking requirements with source files.
- STATUS: Active

### R93: Language-aware parsing of source code (SECTION)

#### SDOC-SRS-142: Language-aware parsing of source code (REQUIREMENT)
StrictDoc shall support parsing the most commonly used formats and programming languages to the Abstract Syntax Tree (AST) level.

The format examples: C, C++, Python, Rust, Ada, Robot, Gherkin, etc.
- RATIONALE: StrictDoc must be capable of traversing the AST of common formats and programming languages to identify and extract function and class markers.

#### SDOC-SRS-146: Language-aware parsing of C/C++ code (REQUIREMENT)
StrictDoc shall support parsing the C and C++ source files which includes:

- Recognizing functions and their Doxygen comments.
- Recognizing function declarations and function definitions.
- STATUS: Active
- RATIONALE: C and C++ languages are common languages for embedded and general systems programming. These languages have to be handled with a dedicated parser because of these languages' specifics.

#### SDOC-SRS-147: Language-aware parsing of Python code (REQUIREMENT)
StrictDoc shall support parsing the Python source files which includes:

- Recognizing Python functions, including nested functions.
- Recognizing Python classes, including nested classes.
- Recognizing decorated functions.
- STATUS: Active
- RATIONALE: Python language has to be handled with a dedicated parser because of this language's specifics.

#### SDOC-SRS-148: Language-aware parsing of Robot framework code (REQUIREMENT)
StrictDoc shall support parsing the Robot framework test files.
- STATUS: Active
- RATIONALE: Robot framework's markup has to be handled with a dedicated parser because of this language's specifics.

### R98: Language-aware parsing of Rust source code (SECTION)

#### SDOC-SRS-164: Auto-scoped relation markers in Rust docs (REQUIREMENT)
If a StrictDoc relation marker is inside a `Rust doc comment`_, the marker scope shall be set to exact the item the Rust
language defines as target of the containing doc comment. The :code:`@relation(scope=...)` parameter shall therefore
be optional and shall be ignored if provided.

.. code-block:: rust
   :number-lines:

   /// @relation(REQ-1)
   impl Foo {

       /// @relation(REQ-2)
       fn foo() {
       }
   }

In the given example, the first marker shall link REQ-1 to the :code:`impl Foo` implementation,
highlighting lines 1 to 7. The second marker shall link REQ-2 to the :code:`fn foo()` function,
highlighting lines 4 to 6.

.. _Rust doc comment: https://doc.rust-lang.org/rust-by-example/meta/doc.html#doc-comments
- NOTES: Note that doc comments are syntactic sugar for `doc attribute`_ s, which shall also be supported.
  To figure detailed doc comment rules from the rust-lang specification it's sometimes useful
  to check for general attribute rules, if explicit doc comment rules are missing.

  .. _doc attribute: https://doc.rust-lang.org/rustdoc/write-documentation/the-doc-attribute.html
- Parent -> SDOC-SRS-34
- Parent -> SDOC-SRS-137

#### SDOC-SRS-165: Inner doc attributes (REQUIREMENT)
StrictDoc shall support relation markers in inner_ `doc attribute`_ s.

.. _inner: https://doc.rust-lang.org/reference/attributes.html#r-attributes.inner
.. _doc attribute: https://doc.rust-lang.org/rustdoc/write-documentation/the-doc-attribute.html#the-doc-attribute
- Parent -> SDOC-SRS-164

#### SDOC-SRS-166: Inner line docs (REQUIREMENT)
StrictDoc shall support auto-scoped relation relation markers in `inner line docs`_.

.. _inner line docs: https://doc.rust-lang.org/reference/comments.html#grammar-INNER_LINE_DOC
- Parent -> SDOC-SRS-164

#### SDOC-SRS-167: Inner block docs (REQUIREMENT)
StrictDoc shall support auto-scoped relation relation markers in `inner block docs`_.

.. _inner block docs: https://doc.rust-lang.org/reference/comments.html#grammar-INNER_BLOCK_DOC
- Parent -> SDOC-SRS-164

#### SDOC-SRS-168: Outer doc attributes (REQUIREMENT)
StrictDoc shall support auto-scoped relation markers in outer_ `doc attribute`_ s.

.. _outer: https://doc.rust-lang.org/reference/attributes.html#r-attributes.outer
.. _doc attribute: https://doc.rust-lang.org/rustdoc/write-documentation/the-doc-attribute.html#the-doc-attribute
- Parent -> SDOC-SRS-164

#### SDOC-SRS-169: Outer line docs (REQUIREMENT)
StrictDoc shall support auto-scoped relation markers in `outer line docs`_.

.. _outer line docs: https://doc.rust-lang.org/reference/comments.html#grammar-OUTER_LINE_DOC
- Parent -> SDOC-SRS-164

#### SDOC-SRS-170: Outer block docs (REQUIREMENT)
StrictDoc shall support auto-scoped relation markers in `outer block docs`_.

.. _outer block docs: https://doc.rust-lang.org/reference/comments.html#railroad-OUTER_BLOCK_DOC
- Parent -> SDOC-SRS-164

#### SDOC-SRS-171: File, line and range markers (REQUIREMENT)
StrictDoc shall point to lines and line ranges of Rust code by using file, line and range markers.
These marker types shall be parsed from `regular line and block comments`_.

Note: File markers may also result from the inner doc comments of the top-level module.

.. _regular line and block comments: https://doc.rust-lang.org/rust-by-example/hello/comment.html#comments
- Parent -> SDOC-SRS-139
- Parent -> SDOC-SRS-124
- Parent -> SDOC-SRS-138

#### SDOC-SRS-172: Source nodes from doc comments (REQUIREMENT)
If a Rust doc comments contains custom tags, and the containing Rust source file matches an entry in the
source node configuration, StrictDoc shall create document nodes from the custom tags and automatically
link the created node with the Rust item targeted by the doc comment.
- Parent -> SDOC-SRS-141

#### SDOC-SRS-173: Forward relations to Rust items (REQUIREMENT)
StrictDoc shall support linking from a requirement in SDoc to a language item in Rust code by using a :code:`FILE`
relation of type :code:`FUNCTION`. For example

.. code-block:: strictdoc

   [REQUIREMENT]
   UID: REQ-1
   - TYPE: File
     VALUE: file.rs
     FUNCTION: file::foo

This shall work for all kinds of Rust items that have a `canonical path`_, including const, enum, fn, mod, static,
struct, trait, type, union.

.. _canonical path: https://doc.rust-lang.org/reference/paths.html#canonical-paths

#### SDOC-SRS-174: Forward relation by canonical path (REQUIREMENT)
The identifier for forward relations shall be the `canonical path`_ as the rustc compiler would set it when invoked for
a single file like

.. code-block:: shell

   rustc --crate-type rlib --emit=obj src/lib.rs

Note: :code:`cargo build` usually result in a different canonical path, since it considers the file position relative to
the crate root. Using a single file as root is a simplification, needed because StrictDoc is unaware of the Rust
file and directory-based module hierarchy.

.. _canonical path: https://doc.rust-lang.org/reference/paths.html#canonical-paths
- NOTES: The canonical path of an item can be observed with :code:`objdump -t lib.o --demangle=rust`. For example, given this
  source file

  .. code-block:: rust
     :number-lines:

     pub mod foo {

         pub trait Foo {
             fn foo(&self) {}
         }

         pub struct Bar(i32);

         impl Foo for Bar {
             fn foo(&self) {}
         }
     }

  :code:`objdump` will show

  .. code-block:: shell

     <lib::foo::Bar as lib::foo::Foo>::foo

  Alas, a forward relation would be

  .. code-block:: strictdoc

     [REQUIREMENT]
     UID: REQ-1
     - TYPE: File
       VALUE: file.rs
       FUNCTION: <lib::foo::Bar as lib::foo::Foo>::foo
- Parent -> SDOC-SRS-173

#### SDOC-SRS-175: Collapse doc comments (REQUIREMENT)
Multiple scattered doc comments shall be collapsed as done by the rustdoc_ tool when using the collapse-docs option
to determine the highlight range(s).

For example, rustdoc would collapse alle these comments into the description of :code:`fn foo()`

.. code-block:: rust
   :number-lines:

   /// Some
   /// line

   /// doc,

   /**
     * and some
     * block dock,
     */

   #[doc = "and some"]

   #[doc = "doc attr."]

   fn foo() {
   }

In the given example, the StrictDoc highlight range for the relation marker shall be from line 1 to line 16.

.. _rustdoc: https://github.com/rust-lang/rust/tree/main/src/tools/rustdoc

#### SDOC-SRS-176: Rust marker descriptions (REQUIREMENT)
StrictDoc should use the marker labels as rustdoc_ would set them in the description of a documented node.

.. _rustdoc: https://doc.rust-lang.org/stable/rustdoc/

#### SDOC-SRS-177: Valid positions of doc comments (REQUIREMENT)
StrictDoc shall find doc comments where the language allows_ them and ignore those in other positions.

.. _allows: https://doc.rust-lang.org/reference/attributes.html#r-attributes.allowed-position
- NOTES: Since doc comments are syntactic sugar for doc attributes, allowed position rules for attributes apply.

#### SDOC-SRS-178: Inner doc comments for functions (REQUIREMENT)
StrictDoc shall find inner doc comments in function blocks.
- Parent -> SDOC-SRS-177

#### SDOC-SRS-179: Inner doc comments for modules (REQUIREMENT)
StrictDoc shall find inner doc comments in module blocks.
- Parent -> SDOC-SRS-177

#### SDOC-SRS-180: Inner doc comments for external blocks (REQUIREMENT)
StrictDoc shall find inner doc comments in external blocks.
- Parent -> SDOC-SRS-177

#### SDOC-SRS-181: Inner doc comments for implementation blocks (REQUIREMENT)
StrictDoc shall find inner doc comments in implementation blocks.
- Parent -> SDOC-SRS-177

#### SDOC-SRS-182: Allowed position for outer docs (REQUIREMENT)
StrictDoc shall find outer doc comments in `allowed positions`_ as specified by the Rust language:

- All item_ declarations
- Most statements
- Block expressions, but only when they are the outer expression of an
  expression statement or the final expression of another block expression.
- Enum variants, struct and union fields
- Generic lifetime or type parameter
- Expressions in limited situations
- Function, closure and function pointer parameters

.. _allowed positions: https://doc.rust-lang.org/reference/attributes.html#r-attributes.allowed-position
.. _item: https://doc.rust-lang.org/reference/items.html#r-items.syntax
- Parent -> SDOC-SRS-177

### SDOC-SRS-143: Link requirements with test files and test reports (REQUIREMENT)
StrictDoc shall support bi-directional linking between requirements, test files, and test reports.
- STATUS: Active
- RATIONALE: Tracing requirements to not just test files but also the test report information closes the verification cycle more completely.

### SDOC-SRS-144: Link requirements with code coverage information (REQUIREMENT)
StrictDoc shall support linking between requirements, source files, and code coverage information.
- STATUS: Active
- RATIONALE: Tracing requirements to not just test files but also to the code coverage information closes the verification cycle more completely.

### R120: Forward linking from requirements to source code (SECTION)

#### SDOC-SRS-145: SDoc markup's forward relations (REQUIREMENT)
StrictDoc shall support forward linking from SDoc nodes to source files.
- RATIONALE: There are cases when it is not possible to modify source code directly. The forward linking enables to refer to the files or their parts from SDoc nodes. Depending on a project structure, the forward linking from requirements to source files can replace the backward linking from source code back to requirements, or both approaches can co-exist.

### R122: Source code markup – Relations (SECTION)

#### SDOC-SRS-34: Relation markers syntax (REQUIREMENT)
StrictDoc shall support annotating source code with links that reference the requirements.
- STATUS: Active

#### SDOC-SRS-124: Line marker (REQUIREMENT)
StrictDoc's shall support line markers that can be attached to single source code lines.

NOTE: A single-line marker points to a single line in a source file.
- STATUS: Active
- RATIONALE: Sometimes a requirement can influence only a single line in the source code. The advantage of a single-line marker compared to a range marker is that a single-line marker is not intrusive and does not clutter source code.

#### SDOC-SRS-137: Function marker (REQUIREMENT)
StrictDoc shall support relation markers that can be attached to individual source code functions.
- STATUS: Active
- RATIONALE: A function is a basic building block of most programming language. It is straightforward to match a source code function to one or more related requirements.

#### SDOC-SRS-140: Class marker (REQUIREMENT)
StrictDoc shall support relation markers that can be attached to source code classes.
- STATUS: Active
- RATIONALE: A class is a basic building block of most programming language. Some requirements can be naturally attached to the whole classes.
- NOTES: Not all programming languages support classes, e.g., C. For these languages and non-code text files, the class markers will have no effect.

#### SDOC-SRS-139: File marker (REQUIREMENT)
StrictDoc's shall support file markers that can be attached to entire source files.
- STATUS: Active
- RATIONALE: There are cases when a requirement can be attached to an entire file.

#### SDOC-SRS-138: Range marker (REQUIREMENT)
StrictDoc shall support relation markers that can be attached to source code ranges.

NOTE: Compared to other marker types, to indicate a range, two markers are needed: one to start a range and one to end a range.
- STATUS: Active
- RATIONALE: There are cases when a requirement implementation results in the requirement affecting only a range/block of source code.

### R129: Source code markup – Nodes (SECTION)

#### SDOC-SRS-141: Parse nodes from source code (REQUIREMENT)
StrictDoc shall support parsing nodes from source code.
- STATUS: Active
- RATIONALE: It can be practical to define the requirement and other nodes directly in source comments and then let a requirements tool generate documents from these nodes' content automatically.

  A reference example: Generating test specifications from the TEST_SPEC nodes which are defined directly in source code comments.

## SECTION-SRS-Export-import-formats: Export/import formats (SECTION)

### SECTION-SRS-RST: RST (SECTION)

#### SDOC-SRS-70: Export to RST (REQUIREMENT)
StrictDoc shall allow exporting SDoc content to the RST format.
- STATUS: Active
- RATIONALE: Exporting SDoc content to RST enables:

  1) Generating RST to Sphinx HTML documentation.
  2) Generating RST to PDF using Sphinx/LaTeX.

#### SDOC-SRS-71: Docutils (REQUIREMENT)
StrictDoc shall generate RST markup to HTML using Docutils.
- STATUS: Active
- RATIONALE: Docutils is the most mature RST-to-HTML converter.
- NOTES: TBD: Move this to design decisions.

### SECTION-SRS-ReqIF: ReqIF (SECTION)

#### SDOC-SRS-72: Export/import from/to ReqIF (REQUIREMENT)
StrictDoc shall support exporting/importing requirements content from/to ReqIF format.
- STATUS: Active

#### SDOC-SRS-73: Standalone ReqIF layer (REQUIREMENT)
StrictDoc shall maintain the core ReqIF implementation as a separate software component.
- STATUS: Active
- RATIONALE: ReqIF is a well-defined standard which exists independently of StrictDoc's development. It is reasonable to maintain the ReqIF codebase as a separate software component to allow independent development and easier maintainability.

### SECTION-SRS-Excel: Excel and CSV (SECTION)

#### SDOC-SRS-74: Export to Excel (REQUIREMENT)
StrictDoc shall allow exporting SDoc documents to Excel, one Excel sheet per document.
- STATUS: Active

#### SDOC-SRS-152: Import from Excel (REQUIREMENT)
StrictDoc shall allow importing Excel documents to SDoc documents, one Excel sheet per document.
- STATUS: Active

#### SDOC-SRS-134: Selected fields export (REQUIREMENT)
StrictDoc Excel export shall allow exporting SDoc documents to Excel with only selected fields.
- STATUS: Active

## SECTION-SRS-Command-line-interface: Command-line interface (SECTION)

### R143: General CLI requirements (SECTION)

#### SDOC-SRS-103: Command-line interface (REQUIREMENT)
StrictDoc shall provide a command-line interface.
- STATUS: Active

### SECTION-SRS-Command-Manage: Command: Manage (SECTION)

#### SECTION-SRS-Command-Auto-UID: Command: Auto UID (SECTION)

##### SDOC-SRS-85: Auto-generate requirements UIDs (REQUIREMENT)
StrictDoc shall allow automatic generation of requirements UIDs.
- STATUS: Active

## R148: Python API (SECTION)

### SDOC-SRS-125: StrictDoc Python API (REQUIREMENT)
StrictDoc shall provide a Python API for its core functions:

- Reading SDoc files
- Creating traceability graph
- Generating HTML exports
- Converting SDoc to other formats.
- STATUS: Active

## R150: Web server (SECTION)

### SDOC-SRS-126: Web server (REQUIREMENT)
StrictDoc shall provide a web server.
- STATUS: Active
- RATIONALE: A web server is a precondition for StrictDoc's web interface. A web server can be available to a single user on their local machine or it can be deployed to a network and be made accessible by several computers.

## R152: User experience (SECTION)

### SDOC-SRS-163: StrictDoc identification (REQUIREMENT)
StrictDoc shall provide 'about' and 'version' commands that display the project's title, current version, license, and links to the project's web pages.
- STATUS: Active

### SECTION-SSRS-Strict-mode-by-default: Strict mode by default (SECTION)

#### SDOC-SRS-6: Warnings are errors (REQUIREMENT)
StrictDoc's default mode of operation shall treat all warnings as errors.
- STATUS: Active
- RATIONALE: When warnings are treated as errors, the user becomes aware of potential issues as soon as they appear.

## SECTION-SRS-Configurability: Configurability (SECTION)

### SDOC-SRS-37: strictdoc.toml file (REQUIREMENT)
StrictDoc shall support a configuration of project-level options through a TOML file named ``strictdoc.toml``.
- STATUS: Active

### SDOC-SRS-39: Feature toggles (REQUIREMENT)
StrictDoc shall allow a user to select a subset of StrictDoc's available features by listing them in the ``strictdoc.toml`` file.
- STATUS: Active

### SDOC-SRS-119: 'Host' parameter (REQUIREMENT)
StrictDoc shall support configuring a host/port on which the StrictDoc web server is run.
- STATUS: Active

## SECTION-SSRS-Performance: Performance (SECTION)

### SDOC-SRS-1: Process-based parallelization (REQUIREMENT)
StrictDoc shall support process-based parallelization for time-critical tasks.
- STATUS: Active
- RATIONALE: Process-based parallelization can provide a good speed-up when several large documents have to be generated.

### SDOC-SRS-95: Caching of parsed SDoc documents (REQUIREMENT)
StrictDoc shall implement caching of parsed SDoc documents.
- STATUS: Active

### SDOC-SRS-2: Incremental generation of documents (REQUIREMENT)
StrictDoc shall support incremental generation of documents.

NOTE: "Incremental" means that only the modified documents are regenerated when StrictDoc is run repeatedly against the same project tree.
- STATUS: Active

### SDOC-SRS-3: Caching of RST fragments (REQUIREMENT)
StrictDoc shall cache the RST fragments rendered to HTML.
- STATUS: Active
- RATIONALE: Conversion of RST markup to HTML is a time consuming process. Caching the rendered HTML of each fragment helps to save time when rendering the HTML content.

### SDOC-SRS-4: On-demand loading of HTML pages (REQUIREMENT)
StrictDoc's web interface shall generate the HTML content only when it is directly requested by a user.
- STATUS: Active
- RATIONALE: Generating a whole documentation tree for a user project can be time consuming. The on-demand loading ensures the "do less work" approach when it comes to rendering the HTML pages.

### SDOC-SRS-5: Precompiled Jinja templates (REQUIREMENT)
StrictDoc shall support a precompilation of HTML templates.
- STATUS: Active
- RATIONALE: The StrictDoc-exported HTML content visible to a user is assembled from numerous small HTML fragments. Precompiling the HTML templates from which the content gets rendered improves the performance of the HTML rendering.

## SECTION-SRS-Quality-requirements: Development process requirements (SECTION)

### R168: General process (SECTION)

#### SDOC-SRS-133: Priority handling of critical issues in StrictDoc (REQUIREMENT)
All critical issues reported in relation to StrictDoc shall be addressed with utmost priority.
- STATUS: Active
- RATIONALE: Prioritizing major issues ensures StrictDoc remains stable and reliable, preventing serious problems that could compromise its performance and integrity.

### SECTION-SRS-Requirements-engineering: Requirements engineering (SECTION)

#### SDOC-SRS-128: Requirements-based development (REQUIREMENT)
StrictDoc's development shall be requirements-based.
- STATUS: Active

#### SDOC-SRS-91: Self-hosted requirements (REQUIREMENT)
StrictDoc's requirements shall be written using StrictDoc.
- STATUS: Active

### SECTION-SRS-Implementation-requirements: Implementation requirements (SECTION)

#### SECTION-SRS-Programming-languages: Programming languages (SECTION)

##### SDOC-SRS-8: Python language (REQUIREMENT)
StrictDoc shall be written in Python.
- STATUS: Active
- RATIONALE: Python has an excellent package ecosystem. It is a widely used language. It is most often the next language for C/C++ programming community when it comes to the tools development and scripting tasks.

#### SECTION-SRS-Cross-platform-availability: Cross-platform availability (SECTION)

##### SDOC-SRS-9: Linux (REQUIREMENT)
StrictDoc shall support the Linux operating systems.
- STATUS: Active

##### SDOC-SRS-10: macOS (REQUIREMENT)
StrictDoc shall support the macOS operating system.
- STATUS: Active

##### SDOC-SRS-11: Windows (REQUIREMENT)
StrictDoc shall support the Windows operating system.
- STATUS: Active

### SECTION-SRS-Implementation-constraints: Implementation constraints (SECTION)

#### SDOC-SRS-89: Use of open source components (REQUIREMENT)
StrictDoc shall be built using only open source software components.
- STATUS: Active
- RATIONALE: No commercial/proprietary dependency chain ensures that StrictDoc remain free and open for everyone.

#### SDOC-SRS-14: No heavy UI frameworks (REQUIREMENT)
StrictDoc shall avoid using large and demanding UI frameworks.

NOTE: An example of frameworks that require a very specific architecture: React JS, AngularJS.
- STATUS: Active

#### SDOC-SRS-15: No use of NPM (REQUIREMENT)
StrictDoc shall avoid extending its infrastructure with anything based on NPM-ecosystem.
- STATUS: Active
- RATIONALE: StrictDoc already deals with the Python/Pip/Pypi ecosystem. The amount of necessary maintenance is already quite high. NPM is known for splitting its projects into very small parts, which increases the complexity of maintaining all dependencies.

#### SDOC-SRS-16: No use of JavaScript replacement languages (e.g., Typescript) (REQUIREMENT)
StrictDoc shall avoid using JavaScript-based programming languages.
- STATUS: Active
- RATIONALE: The development team does not have specific experience with any of the JS alternatives. Staying with a general subset of JavaScript is a safer choice.

#### SDOC-SRS-87: Monolithic application with no microservices (REQUIREMENT)
StrictDoc shall avoid using microservices and microservice-based architectures.
- STATUS: Active
- RATIONALE: The project is too small to scale to a multi-service architecture.
- NOTES: This requirement could be re-considered only if a significant technical pressure
  would require the use of microservices.

#### SDOC-SRS-88: No reliance on containerization (REQUIREMENT)
StrictDoc shall avoid using containers and containerization technologies.
- STATUS: Active
- RATIONALE: Containers are significant extra layer of complexity. They are hard to debug.
- NOTES: This constraint does not block a StrictDoc user from wrapping StrictDoc into their containers.

### SECTION-SRS-Coding-constraints: Coding constraints (SECTION)

#### SDOC-SRS-40: Use of asserts (REQUIREMENT)
StrictDoc's development shall ensure a use of assertions throughout the project codebase.

NOTE: At a minimum, the function input parameters must be checked for validity.
- STATUS: Active

#### SDOC-SRS-41: Use of type annotations in Python code (REQUIREMENT)
StrictDoc's development shall ensure a use of type annotations throughout the project's Python codebase.
- STATUS: Active

### SECTION-SRS-Linting: Linting (SECTION)

#### SDOC-SRS-42: Compliance with Python community practices (PEP8 etc) (REQUIREMENT)
StrictDoc's development shall ensure that the project's codebase is compliant with the Python community's modern practices.
- STATUS: Active

### SECTION-SRS-Static-analysis: Static analysis (SECTION)

#### SDOC-SRS-43: Static type checking (REQUIREMENT)
StrictDoc's development shall include a continuous type checking of StrictDoc's codebase.
- STATUS: Active

### SECTION-SRS-Testing: Testing (SECTION)

#### SDOC-SRS-44: Unit testing (REQUIREMENT)
StrictDoc's development shall provide unit testing of its codebase.
- STATUS: Active

#### SDOC-SRS-45: CLI interface black-box integration testing (REQUIREMENT)
StrictDoc's development shall provide complete black-box integration testing of its command-line interface.
- STATUS: Active

#### SDOC-SRS-46: Web end-to-end testing (REQUIREMENT)
StrictDoc's development shall provide complete end-to-end testing of the web interface.
- STATUS: Active

#### SDOC-SRS-47: At least one integration or end-to-end test (REQUIREMENT)
Every update to the StrictDoc codebase shall be complemented with a corresponding provision of at least one test as follows:

- For web interface: at least one end-to-end test.
- For command-line interface: at least one black-box integration test.
- For internal Python functions: at least one unit test.

NOTE: This requirement implies that no modifications to StrictDoc's functionality can be merged unless accompanied by at least one test.
- STATUS: Active
- RATIONALE: This requirement ensures that every new feature or a chance in the codebase is covered/stressed by at least one test, according to the change type.

## R199: Code hosting and distribution (SECTION)

### SECTION-SRS-Code-hosting: Code hosting (SECTION)

#### SDOC-SRS-12: GitHub (REQUIREMENT)
StrictDoc's source code shall be hosted on GitHub.
- STATUS: Active

### SDOC-SRS-118: StrictDoc license (REQUIREMENT)
All StrictDoc software shall be licensed under the Apache 2 license.
- STATUS: Active
